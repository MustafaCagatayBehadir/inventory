module inventory {

    yang-version 1.1;
    namespace "https://www.turktelekom.com.tr/inventory";
    prefix inv;

    import ietf-inet-types {
        prefix inet;
    }
    import tailf-common {
        prefix tailf;
    }
    import tailf-ncs {
        prefix ncs;
    }

    description
      "Inventory for multi-vendor device inventory management.";

    revision 2023-10-20 {
        description
          "Initial revision.";
    }

    typedef inv-string {
        type string {
            pattern
              '[^\s]+' {
                error-message
                  "No space/s allowed.";
            }
        }
    }

    grouping inventory-action-grouping {
        tailf:action action-update-inventory-manager {
            tailf:info "Update device data into inventory";
            tailf:actionpoint update-inventory-manager;

            input {
                leaf target-devices {
                    tailf:info "Specify device scope for the action";
                    type enumeration {
                        enum all;
                        enum specify;
                    }
                    mandatory true;
                }

                leaf-list device {
                    tailf:info "Fill the list with device(s) the action should run towards";
                    when "../target-devices = 'specify'";
                    type leafref {
                        path "/ncs:devices/ncs:device/ncs:name";
                    }
                    min-elements 1;
                }
            }

            output {
                leaf result {
                    type string;
                }
            }
        }
    }

    grouping platform-grouping {

        leaf name {
            tailf:info "Device Platform Name";
            type string;
        }

        leaf version {
            tailf:info "Device Version";
            type string;
        }

        leaf model {
            tailf:info "Device Model";
            type string;
        }

        leaf serial-number {
            tailf:info "Device Management Address";
            type string;
        }
    }

    grouping inventory-grouping {

        leaf name {
            tailf:info "Module Name";
            type string;
        }

        leaf description {
            tailf:info "Module Description";
            type string;
        }

        leaf pid {
            tailf:info "Module PID";
            type string;
        }

        leaf serial-number {
            tailf:info "Module SN";
            type string;
        }
    }

    grouping controller-grouping {
        leaf id {
            tailf:info "Interface Controller Id";
            type string;
        }

        leaf controller-state {
            tailf:info "Interface Controller State";
            type string;
        }

        leaf optics-type {
            tailf:info "Interface Controller Optical Module Type";
            type string;
        }

        leaf name {
            tailf:info "Interface Controller Optical Module Name";
            type string;
        }

        leaf part-number {
            tailf:info "Interface Controller Optical Module Part Number";
            type string;
        }

        leaf serial-number {
            tailf:info "Interface Controller Optical Module Serial Number";
            type string;
        }

        leaf pid {
            tailf:info "Module PID";
            type string;
        }
    }

    grouping interfaces-grouping {
        leaf if-size {
            tailf:info "Interface Size. Ex GigabitEthernet | TenGigabitEthernet | FortyGigE | HundredGigE | Port-channel";
            type string;
        }

        leaf if-number {
            tailf:info "Interface id. Ex 0/0/0 | 0/0/0/0 | 1";
            type string;
        }
    }

    list inventory-manager {
        description
          "Multi-vendor device inventory management.";
        ordered-by user;

        uses ncs:service-data;
        ncs:servicepoint inventory-manager-servicepoint;

        key name;

        leaf name {
            tailf:info "Inventory Group Name";
            type inv-string;
        }

        list device {

            key name;

            leaf name {
                tailf:info "Device Name";
                type leafref {
                    path "/ncs:devices/ncs:device/ncs:name";
                }
            }

            container platform {
                tailf:info "Device Platform Information";
                config false;
                tailf:cdb-oper {
                    tailf:persistent true;
                }

                uses inv:platform-grouping;
            }

            list inventory {
                tailf:info "Device Module Information";

                config false;
                tailf:cdb-oper {
                    tailf:persistent true;
                }

                key name;

                uses inv:inventory-grouping;
            }

            list controller {
                tailf:info "Interface Controller Status and Configuration";

                config false;
                tailf:cdb-oper {
                    tailf:persistent true;
                }

                key id;

                uses inv:controller-grouping;
            }

            list interface {
                tailf:info "Interface Reference Information";

                key "if-size if-number";

                uses inv:interfaces-grouping;
            }
        }

        uses inv:inventory-action-grouping;
    }
}
